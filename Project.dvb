Attribute VB_Name = "ThisDrawing"
Attribute VB_Base = "0{149DD748-EA85-45A6-93C5-AC50D0260C98}"
Attribute VB_GlobalNameSpace = False
Attribute VB_Creatable = False
Attribute VB_PredeclaredId = True
Attribute VB_Exposed = True
Attribute VB_TemplateDerived = False
Attribute VB_Customizable = True
' Declare a constant double variable
Const pi = 3.14159
Private sp(0 To 2) As Double
Private ep(0 To 2) As Double
Private hwidth As Double
Private trad As Double
Private tspac As Double
Private pangle As Double
Private plength As Double
Private totalwidth As Double
Private angp90 As Double
Private angm90 As Double

' Converts an angular measurement in degrees to radians
' Usage: val = dtr(90)
Function dtr(a As Double) As Double
  dtr = (a / 180) * pi
End Function

' Calculate distance between two points
' Usage: val = distance(point1, point2)
Function distance(sp As Variant, ep As Variant) As Double
  Dim x As Double
  Dim y As Double
  Dim z As Double

  x = sp(0) - ep(0)
  y = sp(1) - ep(1)
  z = sp(2) - ep(2)

  distance = Sqr((Sqr((x ^ 2) + (y ^ 2)) ^ 2) + (z ^ 2))
End Function

' Acquire the information for the garden path
Private Sub gpuser()
  ' Defines a local variant variable
  Dim varRet As Variant

  ' Prompt the user for the start point of the path's centerline
  varRet = ThisDrawing.Utility.GetPoint(, "Specify start point of path: ")
  sp(0) = varRet(0)
  sp(1) = varRet(1)
  sp(2) = varRet(2)

  ' Prompt the user for the endpoint of the path's centerline
  varRet = ThisDrawing.Utility.GetPoint(sp, "Specify endpoint of path: ")
  ep(0) = varRet(0)
  ep(1) = varRet(1)
  ep(2) = varRet(2)

  ' Prompt for half of the path's width
  hwidth = ThisDrawing.Utility.GetDistance(sp, "Specify half width of path: ")

  ' Prompt for the radius of a tile
  trad = ThisDrawing.Utility.GetDistance(sp, "Specify radius of tiles: ")

  ' Prompt for the spacing between the tiles
  tspac = ThisDrawing.Utility.GetDistance(sp, "Specify spacing between tiles: ")

  ' Calculate the angle from the axis
  pangle = ThisDrawing.Utility.AngleFromXAxis(sp, ep)

  ' Multiple by two for the total width of the path
  totalwidth = 2 * hwidth

  ' Calculate the distance of the path
  plength = distance(sp, ep)

  ' Calculate the angle of the path plus or minus 90 degrees
  angp90 = pangle + dtr(90)
  angm90 = pangle - dtr(90)
End Sub

' Draw the outline of the path
Private Sub drawout()
  ' Create an array of four 2D points
  Dim points(0 To 7) As Double

  Dim varRet As Variant
  
  ' Define the start point
  varRet = ThisDrawing.Utility.PolarPoint(sp, angm90, hwidth)
  points(0) = varRet(0)
  points(1) = varRet(1)

  ' Define the second point
  varRet = ThisDrawing.Utility.PolarPoint(varRet, pangle, plength)
  points(2) = varRet(0)
  points(3) = varRet(1)

  ' Define the third point
  varRet = ThisDrawing.Utility.PolarPoint(varRet, angp90, totalwidth)
  points(4) = varRet(0)
  points(5) = varRet(1)

  ' Define the fourth point
  varRet = ThisDrawing.Utility.PolarPoint(varRet, pangle + dtr(180), plength)
  points(6) = varRet(0)
  points(7) = varRet(1)

  ' Draw the outline of the garden path in Model space with a lightweight polyline
  Dim pline As AcadLWPolyline
  Set pline = ThisDrawing.ModelSpace.AddLightWeightPolyline(points)
  
  ' Close the polyline
  pline.Closed = True
End Sub


' Place one row of tiles the given distance along path
' and possibly offset it
Private Sub drow(pd As Double, offset As Double)
  Dim pfirst(0 To 2) As Double
  Dim pctile(0 To 2) As Double
  Dim pltile(0 To 2) As Double
  Dim cir As AcadCircle

  Dim varRet As Variant
  varRet = ThisDrawing.Utility.PolarPoint(sp, pangle, pd)
  pfirst(0) = varRet(0)
  pfirst(1) = varRet(1)
  pfirst(2) = varRet(2)

  varRet = ThisDrawing.Utility.PolarPoint(pfirst, angp90, offset)
  pctile(0) = varRet(0)
  pctile(1) = varRet(1)
  pctile(2) = varRet(2)

  pltile(0) = pctile(0)
  pltile(1) = pctile(1)
  pltile(2) = pctile(2)

  Do While distance(pfirst, pltile) < (hwidth - trad)
    Set cir = ThisDrawing.ModelSpace.AddCircle(pltile, trad)
    varRet = ThisDrawing.Utility.PolarPoint(pltile, angp90, (tspac + trad + trad))
    pltile(0) = varRet(0)
    pltile(1) = varRet(1)
    pltile(2) = varRet(2)
  Loop

  varRet = ThisDrawing.Utility.PolarPoint(pctile, angm90, tspac + trad + trad)
  pltile(0) = varRet(0)
  pltile(1) = varRet(1)
  pltile(2) = varRet(2)

  Do While distance(pfirst, pltile) < (hwidth - trad)
    Set cir = ThisDrawing.ModelSpace.AddCircle(pltile, trad)
    varRet = ThisDrawing.Utility.PolarPoint( _
    pltile, angm90, (tspac + trad + trad))
    pltile(0) = varRet(0)
    pltile(1) = varRet(1)
    pltile(2) = varRet(2)
  Loop
End Sub


' Draw the rows of tiles
Private Sub drawtiles()
  Dim pdist As Double
  Dim offset As Double
  pdist = trad + tspac
  offset = 0

  Do While pdist <= (plength - trad)
    drow pdist, offset
    pdist = pdist + ((tspac + trad + trad) * Sin(dtr(60)))

    If offset = 0 Then
      offset = (tspac + trad + trad) * Cos(dtr(60))
    Else
      offset = 0
    End If
  Loop
End Sub

' Main function that combines the individual Private subroutines
' of the project into a single macro to simplify execution.
Public Sub gardenpath()
  ' Request input from the user
  gpuser

  ' Draws the outline of the garden path
  drawout

  ' Draws the tiles in the outline of the garden path
  drawtiles
End Sub
