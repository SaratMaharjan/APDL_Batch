(DEFUN C:SGVARS ( / )
  (SETVAR "SELECTIONANNODISPLAY" 0)
  (SETVAR "SELECTIONANNODISPLAY" 1)
  (PRINC (GETVAR "LOGINNAME"))
  (IF (= (GETVAR "SELECTIONANNODISPLAY") 1)
    (PRINC "\n Anno display is on")
    (PRINC "\n Anno display is off")
    )
  (PRINC)
  )
